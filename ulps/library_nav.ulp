// library_nav.ulp
// Navigate through library when editing parts
// Allows users to go forward and back in the parts that they have been editing

// Arguments:
// -o for new file open
// -b to navigate back
// -f to navigate forward

// if we are editing a symbol offer to navigate back to a used device set
// if in.a package offer to navigate back to a used device set

int debug = 1;
//string debugLocation = EAGLE_HOME + '/' + "debug.txt";
string debugLocation = "/Users/harry/Desktop/debug.txt";
string cmd = "";
string s = "";
char csvDelimiter = '\t';

string name = "";

// string found = "";
string foundDevicsets[];
int foundDevicesetPtr = 0;

int userSelectedDeviceset = 0;

// first row - current place in navigation
// other rows - library, package / symbol name, 
string fileLocation = EAGLE_DIR + '/' + "library_nav.csv";

int maxNavItems = 10;
string navigateArray[];
int navigateArrayLen = 0;
int currentNavLocation = 1;

// Track if we are on the library contents page
int inLibraryContentsPage = 0;
string currentItemLibrary = "";
string currentItemName = "";
string currentItemType = "";

void clearDebugLog() {
	if (debug) {
	    output(debugLocation, "wt") {}
	}
}

void debugLog(string text) {
    if (debug) {
        output(debugLocation, "at") {
            printf(text);
        }
    }
}

void parseNavigateFile() {
	string _lineSplit[];
	string _tempArray[];
	debugLog("== Parsing navigation file ==\n");

	navigateArrayLen = fileread(_tempArray, fileLocation);
    

	sprintf(s, "Read nav array:\n%s\n", strjoin(_tempArray, '\n'));
    debugLog(s);

	if (navigateArrayLen > 0) {
		for (int i = 0; i < navigateArrayLen; i ++) {
			if (i == 0) {
				// First number is our current location in the nav array
				strsplit(_lineSplit, _tempArray[i], csvDelimiter);
				currentNavLocation = strtol(_lineSplit[1]);
			} else {
				if (strlen(_tempArray[i]) >= 1) {
					navigateArray[i-1] = _tempArray[i];
				}
			}
		}
	}

	// First line in file is current location, so remove one from the array len to reflect the actual len
	navigateArrayLen --;

	sprintf(s, "Read nav array len: %u\n", navigateArrayLen);
    debugLog(s);

	sprintf(s, "parsed nav array:\n%s\n", strjoin(navigateArray, '\n'));
	debugLog(s);
}

void writeNavigateFile() {
    debugLog("== Writing nav file ==\n");
//    sprintf(s, "Nav file location: %s\n", fileLocation);
//    debugLog(s);
    // reset file errors
    fileerror();
    output(fileLocation, "wt") {
//    output(fileLocation, "wt") {
        // Write the navigation file
        printf("current_location%c%u%c\n", csvDelimiter, currentNavLocation, csvDelimiter);
        printf("%s", strjoin(navigateArray, '\n'));
//        for (int i = 0; i >= navigateArrayLen; i++) {
//              printf("%s\n", navigateArray[i]);
//        }
    }

    // If a fileerror occurrs then a proper error message has already been shown to the user
//    if (fileerror()) {
//        exit(0);
//    }
    debugLog("Finished writing nav file\n");
}

int navigateFileExists() {
    debugLog("Testing if navigation file exists\n");
    string _temp[];
    // find out if the navigation file exits
    if (fileglob(_temp, fileLocation) > 0) {
        debugLog("Found navigation file\n");
        return 1;
    } else {
        debugLog("Not found navigation file\n");
        return 0;
    }
}

void getCurrentItem() {
	debugLog("== Get Current Item ==\n");
	// store currently opened item name and library
	library(L) {
		currentItemLibrary = L.name;
	}

	if (symbol) {
		debugLog("In symbol\n");
	    symbol(Q) {
	        currentItemName = Q.name;
	        currentItemType = ".sym";
	    }

	} else if (package) {
		debugLog("In package\n");
	    package(Q) {
	        currentItemName = Q.name;
            currentItemType = ".pac";
        }

	} else if (deviceset) {
		debugLog("In deviceset\n");
        deviceset(Q) {
        	debugLog("In deviceset\n");
	        currentItemName = Q.name;
            currentItemType = ".dev";
        }
    } else {
    	debugLog("In library contents\n");
    	// We are in the main library contents page so set the current item to be blank
    	inLibraryContentsPage = 1;
    	
    }
}

// TODO check if the opened item is the same as the current nav location item

void onFileOpen() {
	debugLog("== File Opened ==\n");
	// Store the current file when opened in a file
	// Read the navigation file into an array
	string _tempArray;
	int _endNavLocation = 0;

	debugLog("New file opened\n");

	if (navigateFileExists()) {
	    // Navigation file exists
	    parseNavigateFile();
	    _endNavLocation = navigateArrayLen + 1;
	}

	sprintf(s, "current nav location: %u\n", currentNavLocation);
    debugLog(s);

    // get details about the current open item
	getCurrentItem();

	// get the last item that is in the nav history csv table
    string _previousItem[];
    int _previousItemIndex = max(0, navigateArrayLen - 1);
    strsplit(_previousItem, navigateArray[_previousItemIndex], csvDelimiter);

    // get the item that is curretly at the currentNavLocation index
    string _currentNavIndexItem[];
    int _currentNavIndexItemIndex = max(0, currentNavLocation - 1);
    strsplit(_currentNavIndexItem, navigateArray[_currentNavIndexItemIndex], csvDelimiter);

    debugLog("Prevoius Item:\n");
    sprintf(s, "%s, %s, %s\n", _previousItem[0], _previousItem[1], _previousItem[2]);
    debugLog(s);

    // if the currently open item is the same as the item at the currentNavLocation index then don't do anything
    // we have probably got here from going forward or back in time

    if (currentItemLibrary == _currentNavIndexItem[0] && currentItemName == _currentNavIndexItem[1] && currentItemType == _currentNavIndexItem[2]) {
    	// current item at the currentNavIndex is the same as the currently open item so don't do anything here
    } else {
	    if (currentItemLibrary != _previousItem[0] || currentItemName != _previousItem[1] || currentItemType != _previousItem[2]) {
	        // Set the current nav location the the end of the array
	        currentNavLocation = _endNavLocation;
	        string _currentItem;
	        sprintf(_currentItem, "%s%c%s%c%s", currentItemLibrary, csvDelimiter, currentItemName, csvDelimiter, currentItemType);

	        if (currentNavLocation <= maxNavItems) {
	            currentNavLocation;
	            navigateArray[currentNavLocation-1] = _currentItem;

	        } else {
	//            navigateArray[0] = '\0';
	            navigateArray[currentNavLocation-1] = _currentItem;
	            currentNavLocation = maxNavItems;
	            debugLog("Max items reached, doing array shuffle\n");

	            // Eagle doesn't allow lowercase letters so setting '\t' as the seperator is valid
	            string _navArrJoin = strjoin(navigateArray, '\t');
	            sprintf(s, "Navigation array joined: %s\n", _navArrJoin);
	            debugLog(s);

	            // find the index of the first occurrence of the '\t' char
	            int _firstItemOffset = strchr(_navArrJoin, '\t');
	            string _navArrSub = strsub(_navArrJoin, _firstItemOffset+1);

	            sprintf(s, "Navigation array substring: %s\n", _navArrSub);
	            debugLog(s);

	            strsplit(navigateArray, _navArrSub, '\t');
	        }

	        sprintf(s, "updated nav array: %s\n", strjoin(navigateArray, ':'));
	        debugLog(s);
	        writeNavigateFile();
	    } else if (currentItemLibrary == _previousItem[0] && currentItemName == _previousItem[1] && currentItemType && _previousItem[2]) {
	    	// If we've opened a file without using the navigation buttons the last item won't be updated if we went back then opened
	    	// the same item again, deal with that here

	    	// Don't write to the array file unless needed
	    	if (currentNavLocation != navigateArrayLen) {
	    		currentNavLocation = navigateArrayLen;
	    		writeNavigateFile();
	    	}
	    }
	}
}


// TODO add error messages if the user tries to navigate beyond the maximum limits of the array
// TODO if item doesnt exist to navigate to then show an error asking user if they want to delete that entry
void navigateForwardBack(int direction) {
	sprintf(s, "== Navigating %s ==\n", direction ? "Forward" : "Back");
	debugLog(s);
	// direction 0 for back, 1 for forward
    if (!navigateFileExists()) {
        // Navigation file doesn't exist
        dlgMessageBox("Could not open navigation file", "&Close");
        exit(1);
    } 

    // Read the navigation file
    parseNavigateFile();
    // get details about the current open item
    getCurrentItem();

    if (direction == 0) {
    	if (currentNavLocation - 1 < 0) {
    		dlgMessageBox("!Can\'t go any further backwards", "&Close");
    		exit(1);
    	} else {
    		currentNavLocation --;
    	}
    	
    } else if (direction == 1) {
    	if (currentNavLocation + 1 > navigateArrayLen) {
    		dlgMessageBox("!Can\'t go any further forwards", "&Close");
    		exit(1);
    	} else {
    		currentNavLocation ++;
    	}

    }

    string _navigateItem[];
    int _navigateItemIndex;

    // At this point we've already taken one off the current nav location
    if (direction == 0) {
    	// Going back
    	if (inLibraryContentsPage == 0) {
    		_navigateItemIndex = max(0, currentNavLocation - 1);
    	} else {
    		_navigateItemIndex = max(0, currentNavLocation);
    		currentNavLocation ++;
    	}
    	
    } else if (direction == 1) {
    	// Going forward
    	if (inLibraryContentsPage == 0) {
			_navigateItemIndex = min(navigateArrayLen - 1, currentNavLocation);
    	} else {
    		_navigateItemIndex = min(navigateArrayLen, currentNavLocation - 1);
    	}
		
    }

    sprintf(s, "Navigate item index: %u\n", _navigateItemIndex);
    debugLog(s);
    
    strsplit(_navigateItem, navigateArray[_navigateItemIndex], csvDelimiter);

    sprintf(s, "Current library: %s, Navigate to library: %s\n", currentItemLibrary, _navigateItem[0]);
    debugLog(s);


    if (currentItemLibrary != _navigateItem[0]) {
    	// We first need to switch libraries
    	debugLog("Moving libraries\n");
    	sprintf(s, "OPEN \'%s\';\n", _navigateItem[0]);
    	cmd += s;
    }

    sprintf(s, "EDIT %s%s;\n", _navigateItem[1], _navigateItem[2]);
    cmd += s;

    debugLog("Opening item: ");
    debugLog(s);

    // write current nav location to the nav file
    writeNavigateFile();

}


// entry point
if (library) {

    clearDebugLog();
	// parse arguments
	if (argc > 1) {
		if (strstr(argv[1], "-b") != -1) {
			// navigate back
			navigateForwardBack(0);
			// Kiss it goodbye
			exit(cmd);

		} else if (strstr(argv[1], "-f") != -1) {
			// navigate forward
			navigateForwardBack(1);
			// Kiss it goodbye
			exit(cmd);

		} else if (strstr(argv[1], "-o") != -1) {
			// debug = 0;
			onFileOpen();
			exit(0);

		}
		
	}

	if (symbol) {
		symbol(SYM) name = SYM.name;

	} else if (package) {
		package(PAC) name = PAC.name;
		sprintf(s, "%s\n", name);
		debugLog(s);
	}



	library(L) {
		L.devicesets(D) {
			if (symbol) {
				D.gates(G) {
					if (strstr(G.symbol.name, name) != -1 && strlen(G.symbol.name) == strlen(name)) {
						foundDevicsets[foundDevicesetPtr] = D.name;
						foundDevicesetPtr ++;
					}
				}
			} else if (package) {
				D.devices(DEV) {
					if (DEV.package) {
					// E.package.name;
					// printf("%s\n", E.name);

						if (strstr(DEV.package.name, name) != -1 && strlen(DEV.package.name) == strlen(name)) {
							foundDevicsets[foundDevicesetPtr] = D.name;
							foundDevicesetPtr ++;
						}
					}
				}
			}
		}
	}

	// if (foundDevicesetPtr > 1) {
		// found more than one device that a symbol belongs to
	
	int _currentRow = 0;
	int result = dlgDialog("Navigate To") {
		dlgVBoxLayout {
				// dlgGroup("Device Set") {
					dlgGridLayout {
						dlgCell(_currentRow, 0) dlgLabel("Found DeviceSets:");
						dlgCell(_currentRow, 1) dlgComboBox(foundDevicsets, userSelectedDeviceset);
						_currentRow ++;

		// 				dlgCell(_currentRow, 0) dlgLabel("Net Class:");
		// 				sprintf(s, "%s", selectedSignal.class.name);
		// 				dlgCell(_currentRow, 1) dlgLabel(s);
		// 				_currentRow ++;

		// 				dlgCell(_currentRow, 0) dlgLabel("Net Class Width:");
		// 				sprintf(s, "%.2fmm", u2mm(_defaultWidth));
		// 				dlgCell(_currentRow, 1) dlgLabel(s);
		// 				sprintf(s, "%.3fin", u2inch(_defaultWidth));
		// 				dlgCell(_currentRow, 2) dlgLabel(s);
		// 				_currentRow ++;

		// 				if (selectedWireWidth > 0) {
		// 					dlgCell(_currentRow, 0) dlgLabel("Wire Width:");
		// 					sprintf(s, "%.2fmm", u2mm(selectedWireWidth));
		// 					dlgCell(_currentRow, 1) dlgLabel(s);
		// 					sprintf(s, "%.3fin", u2inch(selectedWireWidth));
		// 					dlgCell(_currentRow, 2) dlgLabel(s);
		// 					_currentRow ++;
		// 				}

		// 				if (inArgv("-c")) {
		// 					dlgCell(_currentRow, 0) dlgLabel("Net layer:");
		// 					sprintf(s, "%u (%s)", selectedWireLayer, layerToName(selectedWireLayer));
		// 					dlgCell(_currentRow, 1) dlgLabel(s);
		// 					_currentRow++;
		// 				}
					// }
				}

		// 		// dlgStretch(0);
		// 		// dlgGroup("Info") {
		// 		// 	dlgGridLayout {
		// 		// 		dlgCell(0, 0) dlgLabel("Wires in group:");
		// 		// 		sprintf(s, "%u", foundWires);
		// 		// 		dlgCell(0, 1) dlgLabel(s);

		// 		// 		dlgCell(1, 0) dlgLabel("Vias in group:");
		// 		// 		sprintf(s, "%u", foundVias);
		// 		// 		dlgCell(1, 1) dlgLabel(s);
		// 		// 	}
		// 		// }

		// 		if (inArgv("-w")) {
		// 			dlgStretch(0);
		// 			dlgGroup("Change Width") {
		// 				dlgGridLayout {
		// 					dlgCell(0, 0) dlgLabel("Width (mm):");
		// 					dlgCell(0, 1) dlgRealEdit(userSignalWidth, 0.0, 99.0);
		// 				}
		// 			}
		// 		}

		// 		if (inArgv("-c")) {
		// 			buildUsedLayersArray();
		// 			selectedWireLayer --;
		// 			dlgStretch(0);
		// 			dlgGroup("Change Layer") {
		// 				dlgGridLayout {
		// 					dlgCell(0, 0) dlgLabel("Layer:");
		// 					dlgCell(0, 1) dlgComboBox(layerNames, selectedWireLayer);
		// 				}
		// 			}
		// 		}

				dlgStretch(0);
				dlgHBoxLayout {
					dlgPushButton("-&Cancel") dlgReject();
					dlgSpacing(30);
					dlgPushButton("+&Go") dlgAccept();
				}
			}
		};

		if (!result) {
			exit(0);
		}
	// } 

		sprintf(s, "EDIT %s.dev", foundDevicsets[userSelectedDeviceset]);
		cmd += s;

} else {
	dlgMessageBox("!You can only run this ULP from a library", "+&Close");
	exit(1);
}
