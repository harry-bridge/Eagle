// set_title_block.ulp
// Sets information in the title block via attributes in frames on sheets
string titleBlockName = "A3L-LOC";
string titleBlockLibrary = "SmartSentry Frames";

string drawnBy = "";
string projectNum = "";
string revisionNumber = "A1";

int currentSheetNum = 0;
string currentSheetHeadline = "";

string cmd = "";
string s = "";

// Get current title block info for the current sheet
int updateTypeGet = 0;
// Update all title blocks in the document with the same info
int updateTypeUpdate = 1;
// Replace all the title blocks in the document / add them if necessary
int updateTypeReplace = 2;


// errors returned from below function
int noError = 0;
int errorNoFrame = 1;

int generatedFrameCount = 0;

int updateTitleBlockAttrs(int updateType, UL_INSTANCE I, int _sheetNum) {
	int _foundAttrs = 0;

	I.attributes(A) {
		if (A.name == "REV_NUM") {
			
			if (((updateType == updateTypeGet && _sheetNum == currentSheetNum) || updateType == updateTypeReplace)) {
				if (strstr(A.value, ">REV") == -1) {
					_foundAttrs = 1;
					revisionNumber = A.value;
				} 
			}	

			// Apply rev num to all sheets
			if (updateType == updateTypeUpdate) {
				sprintf(s, "ATTRIBUTE %s REV_NUM '%s';\n", I.name, revisionNumber);
				cmd += s;
			}
		}		

		if (A.name == "DRN_BY") {
			if (((updateType == updateTypeGet && _sheetNum == currentSheetNum) || updateType == updateTypeReplace) && strstr(A.value, ">DRN_BY") == -1) {
				drawnBy = A.value;
				_foundAttrs = 1;
			} 

			// Apply to only current sheet being edited
			if (updateType == updateTypeUpdate && _sheetNum == currentSheetNum) {
				sprintf(s, "ATTRIBUTE %s DRN_BY '%s';\n", I.name, drawnBy);
				cmd += s;
			}
		}

		if (A.name == "PROJECT_NUM") { 
			if (((updateType == updateTypeGet && _sheetNum == currentSheetNum) || updateType == updateTypeReplace) && strstr(A.value, ">PROJ") == -1) {
				projectNum = A.value;
				_foundAttrs = 1;
			} 

			// Apply to all sheets
			if (updateType == updateTypeUpdate) {
				sprintf(s, "ATTRIBUTE %s PROJECT_NUM '%s';\n", I.name, projectNum);
				cmd += s;
			}
		}
	}

	return _foundAttrs;
}

int isFrame(UL_PART _part) {
	if (strstr(_part.name, "FRAME") != -1 || strstr(_part.value, "FRAME") != -1) {
		return 1;
	}

	return 0;
}

int updateTitleBlocks(int updateType) {
	int frameX = 0;
	int frameY = 0;
	int frameR = 0;
	string frameName = "";

	// have we found any attributes in previous frames
	int _foundAttrs = 0;
	int _foundFrame = 0;

	schematic(S) {
		S.sheets(Q) {
			// Apply headline only to current sheet
			if (Q.number == currentSheetNum && updateType == updateTypeUpdate) {
				sprintf(s, "DESCRIPTION %s;\n", currentSheetHeadline);
				cmd += s;
			}

			// edit the sheet with the frame on it
			sprintf(s, "EDIT .s%u;\n", Q.number);
			cmd += s;

			Q.parts(P) {
				if (isFrame(P)) {
					// Found a frame on a sheet
					if ((updateType == updateTypeGet && Q.number == currentSheetNum) || updateType == updateTypeReplace) {
						_foundFrame = 1;
						printf("Found frame\n");
					}
  					
					// if the name or the value of the part containes the word frame
					P.instances(I) {
						updateTitleBlockAttrs(updateType, I, Q.number);

						// Store the found frame
						frameName = I.name;
						frameX = I.x;
						frameY = I.y;
						frameR = I.angle;
					}
				}
			}

			if (updateType == updateTypeReplace) {
				if (_foundFrame == 1) {
					// only delete the previous frame if we have found one, otherwise could delete a random object at 0, 0
					sprintf(s, "DELETE %s;\n", frameName);
					cmd += s;
				} 

				sprintf(s, "ADD '%s@%s' R%u (%u %u);\n", titleBlockName, titleBlockLibrary, frameR, frameX, frameY);
				cmd += s;

				// if there was previously a frame on the page, add it's previous attributes back in
				if (_foundFrame == 1) {
					Q.parts(P) {
						if (isFrame(P)) {
							P.instances(I) {
								// pass current sheet number to attr upate to make it upate the drn_by attr on all pages
								updateTitleBlockAttrs(updateTypeUpdate, I, currentSheetNum);
							}
						}
					}
				} else {
					generatedFrameCount ++;
				}

			}

			if (_foundFrame == 0 && updateType == updateTypeGet && Q.number == currentSheetNum) {
				// no frames found
				return errorNoFrame;
			}

			// next page, no found frames
			_foundFrame = 0;
		}
	}

	sprintf(s, "EDIT .s%u;\n", currentSheetNum);
	cmd += s;

	return noError;
}

void showOptions() {
	int _result = dlgDialog("Title Block Info") {
		dlgVBoxLayout {
			dlgGroup("Global attributes") {
				dlgGridLayout {
					dlgCell(0, 0) dlgLabel("Drawn By");
					dlgCell(0, 1, 0, 4) dlgStringEdit(drawnBy);
					dlgCell(1, 0) dlgLabel("Project Number");
					dlgCell(1, 1, 1, 4) dlgStringEdit(projectNum);
					dlgCell(2, 0) dlgLabel("Revision Number");
					dlgCell(2, 1, 2, 4) dlgStringEdit(revisionNumber);
				}
			}

			dlgGroup("Sheet attributes") {
				dlgGridLayout {
					dlgCell(0, 0) dlgLabel("Current sheet");
					sprintf(s, "%u", currentSheetNum);
					dlgCell(0, 1) dlgLabel(s);
					dlgCell(1, 0) dlgLabel("Heading");
					dlgCell(1, 1, 1, 4) dlgStringEdit(currentSheetHeadline);
				}
			}

			dlgSpacing(10);
			dlgStretch(0);

			dlgHBoxLayout {
				dlgPushButton("-&Cancel") dlgReject();
				dlgPushButton("+&OK") dlgAccept();
				}
			// dlgStretch(1);
			}
		};

	if (_result == 0) {
		exit (0);
	} 
}

// springf(s, "%s/debug.txt", EAGLE_HOME);
output("/Users/harry/Desktop/debug.txt", "wt") {
// entry point
	// printf("%s %s\n", argv[0], argv[1]);	
if (schematic) {
	int ret = 0;

	schematic(S) {
		sheet(SH) currentSheetNum = SH.number;
		sheet(SH) currentSheetHeadline = SH.headline;
	}

	printf("Current sheet: %u\n", currentSheetNum);
	printf("Current sheet headline: %s\n", currentSheetHeadline);

	if (strstr(argv[1], "-r") != -1) {
		// replaceTitleBlocks();
		updateTitleBlocks(updateTypeReplace);

		sprintf(s, "RUN %s -u;\n", argv[0]);
		cmd += s;

		string plural = "";
		if (generatedFrameCount != 1) plural = "s";

		sprintf(s, ";Adding %u new title block%s.\nCheck new title block%s.", generatedFrameCount, plural, plural);
		dlgMessageBox(s, "+&Ok");

	} else if (strstr(argv[1], "-u") != -1) {
		int _actualCurrentSheet = currentSheetNum;

		schematic(SC) {
			SC.sheets(S) {
				S.parts(P) {
					if (isFrame(P)) {
						P.instances(I) {
							// pass current sheet number to attr upate to make it upate the drn_by attr on all pages
							currentSheetNum = S.number;
							// edit the sheet with the frame on it
							sprintf(s, "EDIT .s%u;\n", S.number);
							cmd += s;
							if (updateTitleBlockAttrs(updateTypeGet, I, S.number) == 0) {
								// found a new title block on a sheet, set the drn_by to default value
								drawnBy = ">DRN_BY";
							}

							updateTitleBlockAttrs(updateTypeUpdate, I, S.number);
						}
					}
				}
			}
		}

		sprintf(s, "EDIT .s%u;\n", _actualCurrentSheet);
		cmd += s;

	} else {
		ret = updateTitleBlocks(updateTypeGet);

		if (ret == errorNoFrame) {
			if (dlgMessageBox("!No valid frames found on current sheet.\nDo you want to add one?", "-&Exit", "+&Yes") == 1) {
				cmd = "";
				updateTitleBlocks(updateTypeReplace);
			} else {
				exit(0);
			}
		}
		
		showOptions();
		updateTitleBlocks(updateTypeUpdate);
	}

} else {
	dlgMessageBox("!You can only run this ULP from a schematic", "+&Close");
	exit(0);
}
}
exit(cmd);
